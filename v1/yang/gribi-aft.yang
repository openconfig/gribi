module gribi-aft {
  // Copyright 2021 The OpenConfig Authors 
  //
  // Licensed under the Apache License, Version 2.0 (the "License");
  // you may not use this file except in compliance with the License.
  // You may obtain a copy of the License at
  //
  //      http://www.apache.org/licenses/LICENSE-2.0
  //
  // Unless required by applicable law or agreed to in writing, software
  // distributed under the License is distributed on an "AS IS" BASIS,
  // WITHOUT WARRANTIES OR CONDITIONS OF ANY KIND, either express or implied.
  // See the License for the specific language governing permissions and
  // limitations under the License.

  namespace "http://github.com/openconfig/gribi/v1/yang/gribi/aft";
  prefix "gaft";

  import openconfig-extensions { prefix "oc-ext"; }
  import openconfig-aft { prefix "oc-aft"; }

  organization
    "OpenConfig working group";

  contact
    "www.openconfig.net";

  description
    "This module defines the gRIBI API. It is used to generate
    the protobuf definition of the schema that is used in the
    protocol.";

  oc-ext:openconfig-version "1.1.0";

  revision "2026-11-12" {
    description
      "Update to openconfig-aft 3.8.0. Deviate GRE dscp, and GRE and UDP
      in-profile-dscp and out-profile-dscp as they are not supported in
      this release.";
    reference "1.1.0";
  }

  revision "2026-10-13" {
    description
      "Add versioning of gribi-aft.yang. Deviate mpls-label-stack and 
      encap-mpls-label-stack as they are not supported in this release.";
    reference "1.0.0";
  }

  uses oc-aft:aft-top;

  deviation "/afts/next-hops/next-hop/state/origin-protocol" {
    description
      "Next-hop origin protocol is not a field that can be programmed
      via gRIBI.";
    deviate not-supported;
  }

  deviation "/afts/ipv4-unicast/ipv4-entry/state/origin-protocol" {
    description
      "IPv4 origin protocol is not a field that can be programmed
      via gRIBI.";
    deviate not-supported;
  }

  deviation "/afts/ipv6-unicast/ipv6-entry/state/origin-protocol" {
    description
      "IPv6 origin protocol is not a field that can be programmed
      via gRIBI.";
    deviate not-supported;
  }

  deviation "/afts/next-hops/next-hop/state/lsp-name" {
    description
      "RSVP-TE LSP name is not a field that can be programmed
      via gRIBI.";
    deviate not-supported;
  }

  deviation "/afts/next-hop-groups/next-hop-group/conditional" {
    description
      "Conditional next-hop groups (used to represent CBTS or PBTS)
      are not currently supported by gRIBI.";
    deviate not-supported;
  }

  deviation "/afts/ipv4-unicast/ipv4-entry/state/counters" {
    description
      "Packet counters are not accessible over gRIBI, and rather
      over gNMI for the AFT model.";
    deviate not-supported;
  }

  deviation "/afts/ipv6-unicast/ipv6-entry/state/counters" {
    description
      "Packet counters are not accessible over gRIBI, and rather
      over gNMI for the AFT model.";
    deviate not-supported;
  }

  deviation "/afts/policy-forwarding/policy-forwarding-entry/state/counters" {
    description
      "Packet counters are not accessible over gRIBI, and rather
      over gNMI for the AFT model.";
    deviate not-supported;
  }

  deviation "/afts/mpls/label-entry/state/counters" {
    description
      "Packet counters are not accessible over gRIBI, and rather
      over gNMI for the AFT model.";
    deviate not-supported;
  }

  deviation "/afts/ethernet/mac-entry/state/counters" {
    description
      "Packet counters are not accessible over gRIBI, and rather
      over gNMI for the AFT model.";
    deviate not-supported;
  }

  deviation "/afts/next-hops/next-hop/state/counters" {
    description
      "Packet counters are not accessible over gRIBI, and rather
      over gNMI for the AFT model.";
    deviate not-supported;
  }

  deviation "/afts/next-hop-groups/next-hop-group/state/programmed-id" {
    description
      "Next Hop Group programmed IDs are not accessible over gRIBI,
       and rather over gNMI for the AFT model.";
    deviate not-supported;
  }

  deviation "/afts/next-hops/next-hop/state/programmed-index" {
    description
      "Next Hop programming indices are not accessible over gRIBI,
       and rather over gNMI for the AFT model.";
    deviate not-supported;
  }

  deviation "/afts/state-synced" {
    description
      "state-synced is not accessible over gRIBI but rather over gNMI via
       the AFT model.";
    deviate not-supported;
  }

  deviation "/afts/next-hop-groups/next-hop-group/state/next-hop-group-name" {
    description
      "Next hop group name is only set by a device and is not accessible over
      gRIBI, but rather over gNMI via the AFT model.";
    deviate not-supported;
  }

  deviation "/afts/next-hop-groups/next-hop-group/state/backup-active" {
    description
      "Backup active is only set by a device and is not accessible over gRIBI,
      but rather over gNMI via the AFT model.";
    deviate not-supported;
  }

  deviation "/afts/next-hops/next-hop/encap-headers/encap-header/vxlan" {
    description
      "VXLAN header encapsulation is not accessible over gRIBI.";
    deviate not-supported;
  }

  deviation "/afts/mpls/label-entry/decap-mpls-label-stacks" {
    description
      "Decapsulation of MPLS label stacks is not supported in this release of
      gRIBI.  A future release of gRIBI could add support for this leaf.";
    deviate not-supported;
  }

  deviation "/afts/next-hops/next-hop/encap-headers/encap-header/mpls/encap-mpls-label-stacks" {
    description
      "Encapsulation of MPLS label stacks is not supported in this release of
      gRIBI.  A future release of gRIBI could add support for this leaf.";
    deviate not-supported;
  }

  deviation "/afts/next-hops/next-hop/gre/state/dscp" {
    description
      "GRE DSCP is not supported in this release of gRIBI.
      A future release of gRIBI could add support for this leaf.";
    deviate not-supported;
  }

  deviation "/afts/next-hops/next-hop/gre/state/in-profile-dscp" {
    description
      "GRE in-profile DSCP is not supported in this release of gRIBI.
      A future release of gRIBI could add support for this leaf.";
    deviate not-supported;
  }

  deviation "/afts/next-hops/next-hop/gre/state/out-profile-dscp" {
    description
      "GRE out-profile DSCP is not supported in this release of gRIBI.
      A future release of gRIBI could add support for this leaf.";
    deviate not-supported;
  }

  deviation "/afts/next-hops/next-hop/encap-headers/encap-header/gre/state/dscp" {
    description
      "GRE DSCP is not supported in this release of gRIBI.
      A future release of gRIBI could add support for this leaf.";
    deviate not-supported;
  }

  deviation "/afts/next-hops/next-hop/encap-headers/encap-header/gre/state/in-profile-dscp" {
    description
      "GRE in-profile DSCP is not supported in this release of gRIBI.
      A future release of gRIBI could add support for this leaf.";
    deviate not-supported;
  }

  deviation "/afts/next-hops/next-hop/encap-headers/encap-header/gre/state/out-profile-dscp" {
    description
      "GRE out-profile DSCP is not supported in this release of gRIBI.
      A future release of gRIBI could add support for this leaf.";
    deviate not-supported;
  }

  deviation "/afts/next-hops/next-hop/encap-headers/encap-header/udp-v4/state/in-profile-dscp" {
    description
      "UDP in-profile DSCP is not supported in this release of gRIBI.
      A future release of gRIBI could add support for this leaf.";
    deviate not-supported;
  }

  deviation "/afts/next-hops/next-hop/encap-headers/encap-header/udp-v4/state/out-profile-dscp" {
    description
      "UDP out-profile DSCP is not supported in this release of gRIBI.
      A future release of gRIBI could add support for this leaf.";
    deviate not-supported;
  }

  deviation "/afts/next-hops/next-hop/encap-headers/encap-header/udp-v6/state/in-profile-dscp" {
    description
      "UDP in-profile DSCP is not supported in this release of gRIBI.
      A future release of gRIBI could add support for this leaf.";
    deviate not-supported;
  }

  deviation "/afts/next-hops/next-hop/encap-headers/encap-header/udp-v6/state/out-profile-dscp" {
    description
      "UDP out-profile DSCP is not supported in this release of gRIBI.
      A future release of gRIBI could add support for this leaf.";
    deviate not-supported;
  }

  grouping entry-nhg-extensions {
    description
      "Leaves that are added as references in the openconfig-aft-network-instance
      module to the /network-instance hierarchy, but are handled differntly in
      the gRIBI model which does not include the network-instance YANG hierarchy.";

    leaf next-hop-group {
      type uint64;
      description
        "Identifier for the next-hop-group that is to be used for the
        entry. In gRIBI, this value is expressed as a integer value
        directly. The wider openconfig-network-instance model expresses
        the relationships to other network instances as part of
        telemetry.";
    }

    leaf next-hop-group-network-instance {
      type string;
      description
        "Identifier for the network-instance within which the next-hop-group
        is to be resolved. In gRIBI this is the string name of the network
        instance, rather than a reference as is used in telemetry.";
    }
  }

  augment "/afts/next-hops/next-hop/state" {
    description
     "Add network-instance references to next-hop.";

    leaf network-instance {
      type string;
      description
        "The network instance within which the network instance is to be resolved.";
    }
  }

  augment "/afts/ipv4-unicast/ipv4-entry/state" {
    description
      "Add the NHG reference extensions to IPv4 unicast.";
    uses entry-nhg-extensions;
  }

  augment "/afts/ipv6-unicast/ipv6-entry/state" {
    description
      "Add the NHG reference extensions to IPv6 unicast.";
    uses entry-nhg-extensions;
  }

  augment "/afts/mpls/label-entry/state" {
    description
      "Add the NHG reference extensions to MPLS.";
    uses entry-nhg-extensions;
  }

  augment "/afts/policy-forwarding/policy-forwarding-entry/state" {
    description
      "Add the NHG reference extensions to policy-forwarding.";
    uses entry-nhg-extensions;
  }

  augment "/afts/ethernet/mac-entry/state" {
    description
      "Add the NHG reference extensions to Ethernet.";
    uses entry-nhg-extensions;
  }
}
