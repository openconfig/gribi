module gribi-v1-augments {
  // Copyright 2021 The OpenConfig Authors 
  //
  // Licensed under the Apache License, Version 2.0 (the "License");
  // you may not use this file except in compliance with the License.
  // You may obtain a copy of the License at
  //
  //      http://www.apache.org/licenses/LICENSE-2.0
  //
  // Unless required by applicable law or agreed to in writing, software
  // distributed under the License is distributed on an "AS IS" BASIS,
  // WITHOUT WARRANTIES OR CONDITIONS OF ANY KIND, either express or implied.
  // See the License for the specific language governing permissions and
  // limitations under the License.

  namespace "http://github.com/openconfig/gribi/v1/yang/gribi/aft-augments";
  prefix "gaft-augments";

  import gribi-aft { prefix "gaft"; }
  import openconfig-inet-types { prefix "oc-inet"; }

  description
    "This module describes augmentations to the OpenConfig AFT schema
    that are made for gRIBI. These changes are to be upstreamed to the
    public OpenConfig models where possible.";

  grouping nhg-network-instance {
    description
      "Add a reference to the network-instance within which a next-hop-group
      is to be resolved.";
    
    leaf next-hop-group-network-instance {
      // TODO(robjs): When this is upstreamed we should likely use a leafref
      // and then a deviate/replace to use string here (since the leafref
      // will not resolve in the gribi-aft context).
      type string;
      description
        "The network-instance to look up the next-hop-group in. If unspecified
        the next-hop-group is resolved within the default network instance.
        The referenced network-instance must be an existing network-instance
        on the device and have corresponding entries in the
        /network-instances/network-instance list.";
    }
  }

  augment "/gaft:afts/gaft:ipv4-unicast/gaft:ipv4-entry/gaft:state" {
    description
      "Add NHG NI to IPv4 entries.";
    uses nhg-network-instance;
  }

  grouping nh-ni {
    description
      "Add a reference to the network-instance within which a next-hop is
      to be resolved.";

    leaf network-instance {
      // TODO(robjs): When upstreamed, similarly to the the NHG NI, this should
      // likely be a leafref with the same deviation applied.
      type string;
      description
        "Network instance for the next-hop. If the value of this field is not
        specified, the next-hop is looked up in the same network-instance as
        the entry is populated within.";
    }
  }

  augment "/gaft:afts/gaft:next-hops/gaft:next-hop/gaft:state" {
    description
      "Add NI reference to NH";
    uses nh-ni;
  }

  grouping entry-metadata {
    description
      "Add persistent metadata to an entry.";
    
    leaf metadata { 
      type binary {
        length 8; // 8 bytes
      }
      description
        "Metadata persistently stored with the entry.";
    }
  }

  augment "/gaft:afts/gaft:ipv4-unicast/gaft:ipv4-entry/gaft:state" {
    description
      "Add metadata to IPv4 entries.";
    uses entry-metadata;
  }

  grouping nh-ipip {
    description
      "IP-in-IP encapsulation applied on a next-hop";

    container ip-in-ip {
      description
        "When specified, the packet has an IP-in-IP header applied to it before
        forwarding to the specified next-hop.";

      leaf src-ip {
        type oc-inet:ip-address;
        description
          "Source IP address to use for the encapsulated packet.";
      }

      leaf dst-ip {
        type oc-inet:ip-address;
        description
          "Destination IP address to use for the encapsulated packet.";
      }
    }
  }

  augment "/gaft:afts/gaft:next-hops/gaft:next-hop/gaft:state" {
    description
      "Add IP-in-IP to next-hop";
    uses nh-ipinip;
  }
}
