module gribi-aft {
  // Copyright 2017 Google Inc.
  //
  // Licensed under the Apache License, Version 2.0 (the "License");
  // you may not use this file except in compliance with the License.
  // You may obtain a copy of the License at
  //
  //      http://www.apache.org/licenses/LICENSE-2.0
  //
  // Unless required by applicable law or agreed to in writing, software
  // distributed under the License is distributed on an "AS IS" BASIS,
  // WITHOUT WARRANTIES OR CONDITIONS OF ANY KIND, either express or implied.
  // See the License for the specific language governing permissions and
  // limitations under the License.

  namespace "http://google.com/yang/gribi/aft";
  prefix "gaft";

  import openconfig-aft { prefix "oc-aft"; }

  organization
      "Google, Inc.";

  contact
      "robjs@google.com";

  description
      "This module defines the gRIBI API. It is used to generate
      the protobuf definition of the schema that is used in the
      protocol.

      TODO(robjs): This module needs to self-augment to add the
      relevant config containers to the AFT schema. At the moment
      this is achieved through path compression, which means directly
      using the YANG schema is not actually possible.";

  uses oc-aft:aft-top;
}
